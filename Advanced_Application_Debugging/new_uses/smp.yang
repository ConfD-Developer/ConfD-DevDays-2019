module smp {
  namespace "http://tail-f.com/ns/example/smp";
  prefix smp;

  import ietf-inet-types {
    prefix inet;
  }
  import tailf-common {
    prefix tailf;
  }

  /*    A set of server structures  */
  container servers {
    tailf:callpoint simplecp;
    
    list server {
      key name;
      //    max-elements 64;
      leaf name {
        type string;
      }
      leaf ip {
        type inet:ip-address;
        mandatory true;
      }
      leaf port {
        type inet:port-number;
        mandatory true;
      }
    }
  }    

  list obj { 
    key name; 
    leaf name { 
      type string;
    }
    leaf A { 
      type int32;
    }
    leaf B {
      type int32;
    }
    leaf C {
      tailf:validate vp {
	tailf:dependency "../B";
	tailf:dependency "../A";
      }
      type int32;
    }
  }
}
