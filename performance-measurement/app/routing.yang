module routing {
  namespace "http://tail-f.com/ns/example/routing";
  prefix routing;

  organization "Tail-f";
  description
    "An example module";


  revision 2019-10-14 {
    description
      "Initial revision.";
  }

  container sys {
    container interfaces {
      list interface {
        key "name";
        leaf name {
          type string;
        }
      }
    }
  }
}
